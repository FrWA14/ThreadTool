# -*- coding: utf-8 -*-
# Installe (ou met à jour) l'extension ThreadTool dans FreeCAD — Windows, Linux et macOS.
# Installs (or updates) the ThreadTool add-on in FreeCAD — Windows, Linux and macOS.
# Messages en français si FreeCAD est en français, sinon en anglais.
#
# Utilisation : dans FreeCAD, menu Macro → Macros… → « Fichier utilisateur… » ou
# Fichier → Ouvrir ce fichier, puis bouton « Exécuter la macro » (▶).
# La macro cherche, à côté d'elle, le dossier « ThreadTool » ou une archive « ThreadTool*.zip ».
# Sinon, elle demande où se trouve l'archive.

import os
import glob
import shutil
import zipfile
import tempfile

import FreeCAD as App

NAME = "ThreadTool"


def _french():
    """FreeCAD (ou le système, si FreeCAD suit le système) est-il en français ?"""
    try:
        import FreeCADGui
        return FreeCADGui.supportedLocales().get(FreeCADGui.getLocale(), "").startswith("fr")
    except Exception:
        name = App.ParamGet("User parameter:BaseApp/Preferences/General").GetString("Language")
        if name:
            return name == "French"
        import locale
        return (locale.getlocale()[0] or "").startswith("fr")


FR = _french()


def T(fr, en):
    return fr if FR else en


def _here():
    try:
        return os.path.dirname(os.path.abspath(__file__))
    except NameError:
        return os.getcwd()


def _is_module_dir(path):
    return os.path.isfile(os.path.join(path, "InitGui.py")) and os.path.isdir(os.path.join(path, "threadtool"))


def _find_in_zip(zpath, tmp):
    """Extrait l'archive et retourne le dossier du module qu'elle contient."""
    with zipfile.ZipFile(zpath) as z:
        z.extractall(tmp)
    for root, dirs, files in os.walk(tmp):
        if _is_module_dir(root):
            return root
    return None


def _ask_zip():
    if not App.GuiUp:
        return None
    from PySide import QtWidgets
    import FreeCADGui as Gui
    path, _ = QtWidgets.QFileDialog.getOpenFileName(
        Gui.getMainWindow(), T("Archive ThreadTool", "ThreadTool archive"), _here(),
        T("Archive ThreadTool (*.zip)", "ThreadTool archive (*.zip)"))
    return path or None


def _message(text, error=False):
    App.Console.PrintError(text + "\n") if error else App.Console.PrintMessage(text + "\n")
    if App.GuiUp:
        from PySide import QtWidgets
        import FreeCADGui as Gui
        box = QtWidgets.QMessageBox.critical if error else QtWidgets.QMessageBox.information
        box(Gui.getMainWindow(), T("Installation de ThreadTool", "ThreadTool installation"), text)


def install(source=None):
    tmp = tempfile.mkdtemp(prefix="threadtool_")
    try:
        src = None
        candidates = [source] if source else [os.path.join(_here(), NAME), _here()]
        for c in candidates:
            if c and os.path.isdir(c) and _is_module_dir(c):
                src = c
                break
        if src is None:
            zips = [source] if source and source.lower().endswith(".zip") else \
                sorted(glob.glob(os.path.join(_here(), NAME + "*.zip")))
            if not zips:
                z = _ask_zip()
                zips = [z] if z else []
            for z in zips:
                src = _find_in_zip(z, tmp)
                if src:
                    break
        if src is None:
            _message(T("Dossier ou archive ThreadTool introuvable à côté de la macro.",
                       "ThreadTool folder or archive not found next to the macro."), error=True)
            return False
        mod = os.path.join(App.getUserAppDataDir(), "Mod")
        dest = os.path.join(mod, NAME)
        if os.path.realpath(src) == os.path.realpath(dest):
            _message(T("ThreadTool est déjà installé à cet endroit :\n%s", "ThreadTool is already installed here:\n%s") % dest)
            return True
        os.makedirs(mod, exist_ok=True)
        if os.path.islink(dest):
            os.unlink(dest)
        elif os.path.isdir(dest):
            shutil.rmtree(dest)
        shutil.copytree(src, dest, ignore=shutil.ignore_patterns("__pycache__", "*.pyc", ".git", "dist"))
        _message(T("ThreadTool est installé dans :\n%s\n\nRedémarre FreeCAD, puis ouvre l'atelier Part Design : "
                   "l'icône « Filetage / taraudage » est à côté de « Perçage ».",
                   "ThreadTool is installed in:\n%s\n\nRestart FreeCAD, then open the Part Design workbench: "
                   "the \"Thread / tap\" icon is next to \"Hole\".") % dest)
        return True
    except Exception as e:
        _message(T("Échec de l'installation : %s", "Installation failed: %s") % e, error=True)
        return False
    finally:
        shutil.rmtree(tmp, ignore_errors=True)


install(os.environ.get("THREADTOOL_SOURCE") or None)
